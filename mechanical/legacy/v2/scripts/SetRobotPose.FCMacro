from pathlib import Path
import sys
import FreeCAD as App
import FreeCADGui as Gui
sys.path.insert(0,str(Path(__file__).resolve().parent))
import build_robot_master as robot
doc=App.ActiveDocument
if not doc or not doc.getObject("PoseController"):
    raise ValueError("Open Robot_Master.FCStd first")
cfg=robot.Robot_LoadConfig()
for key in cfg["dimensions"]:
    cfg["dimensions"][key]=float(doc.MasterParameters.get(key))
# Select PoseController.CurrentPose in the property editor, then run this macro.
robot.Robot_SetPose(doc,str(doc.PoseController.CurrentPose),cfg)
Gui.activeDocument().activeView().viewAxonometric()
Gui.activeDocument().activeView().fitAll()
